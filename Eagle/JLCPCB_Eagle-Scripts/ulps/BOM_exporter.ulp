/*
 BOM_exporter.ulp
 DvidMakesThings
 https://github.com/DvidMakesThings
*/

// map of Eagle SMD layers
int layer_id_map[]      = { 1, 16 };
string layer_name_map[] = { "Top", "Bottom" };

// storage for selected parts + their side
UL_ELEMENT selected_elements[];
int        selected_side[];

string replace_commas(string s) {
    while (strstr(s, ",") >= 0) {  // convert commas to spaces
        string substitution_string = " ";
        sprintf(s, "%s%s%s",
            strsub(s, 0, strstr(s, ",")),
            substitution_string,
            strsub(s, strstr(s, ",")+1)
        );
    }
    return s;
}

if (board) board(B) {
    int skip_empty = 1;   // set to 0 if you want parts with blank values
    string outdir = dlgDirectory("Export files to", filedir(B.name));
    if (outdir == "") exit(0);

    // collect every populated element, detect its side
    int count = 0;
    B.elements(E) if (E.populate) {
        selected_elements[count] = E;

        // default to Top
        int side = 0;
        E.package.contacts(C) {
            if (C.smd && C.smd.layer == layer_id_map[1]) {
                side = 1;
                break;
            }
        }
        selected_side[count] = side;
        count++;
    }

    // base filename (no extension)
    string base = outdir + "/"
        + strsub(filename(B.name), 0, strlen(filename(B.name)) - 4);

    string cpl_file = base + "_centroid.xls";
    string bom_file = base + "_bom.csv";   

    //
    // 1) CPL
    //
    output(cpl_file) {
        printf("### Module positions export ###\n");
        printf("### Printed by EAGLE ULP ###\n");
        printf("### Unit = mm, Angle = deg.\n");
        printf("# Ref,Val,Package,PosX,PosY,Rot,Side\n");

        for (int i = 0; i < count; i++) {
            UL_ELEMENT E = selected_elements[i];
            int side = selected_side[i];
            if (skip_empty && E.value == "") continue;

            int angle = E.angle;
            E.attributes(A) {
                if (A.name == "NEXTPCB_ROT" || A.name == "NEXTPCB_ROTATION")
                    angle += strtol(A.value);
            }
            if (side == 1)
                angle = (360 - angle + 180) % 360;
            real ang = angle;

            string side_s = (side == 0) ? "top" : "bottom";

            printf("%s,%s,%s,%.4f,%.4f,%.4f,%s\n",
                   E.name,
                   replace_commas(E.value),
                   replace_commas(E.package.name),
                   u2mm(E.x),
                   u2mm(E.y),
                   ang,
                   side_s);
        }
    }

    //
    // 2) BOM 
    //
    output(bom_file) {
        // Header line
        printf("Designator;Quantity;Manufacturer Part Number;Manufacturer;Package/Footprint;Description;Procurement Type;Customer Note\n");

        int            indexes[];
        numeric string keys[];   // HQ_PART or MPN as key

        for (int i = 0; i < count; i++) {
            string mpn = "";
            selected_elements[i].attributes(A) {
                if (A.name == "HQ_PART") mpn = replace_commas(A.value);
                if (mpn == "" && A.name == "MPN") mpn = replace_commas(A.value);
            }
            keys[i] = mpn;
            indexes[i] = i;
        }
        sort(count, indexes, keys);

        string curr_mpn     = "";
        string curr_mfr     = "";
        string curr_pkg     = "";
        string curr_desc    = "";
        string curr_proc    = "";
        string curr_note    = "";
        string designators  = "";
        int    qty          = 0;
        int    notstarting  = 0;

        for (int j = 0; j < count; j++) {
            UL_ELEMENT E = selected_elements[indexes[j]];
            if (skip_empty && E.value == "") continue;

            string mpn = "";
            string mfr = "";
            string desc = "";
            string proc = "";
            string note = "";

            E.attributes(A) {
                if (A.name == "HQ_PART") mpn = replace_commas(A.value);
                if (mpn == "" && A.name == "MPN") mpn = replace_commas(A.value);
                if (A.name == "MANUFACTURER") mfr = replace_commas(A.value);
                if (A.name == "DESCRIPTION") desc = replace_commas(A.value);
                if (A.name == "PROCUREMENT") proc = replace_commas(A.value);
                if (A.name == "CUSTOMER_NOTE") note = replace_commas(A.value);
            }

            // If value is DNI → force Procurement Type = DNP
            string val_u = strupr(E.value);
            if (val_u == "DNI") {
                proc = "DNP";
            }

            // Group only by MPN
            if (notstarting && (mpn != curr_mpn)) {
                // flush
                printf("%s;", designators);
                printf("%d;", qty);
                printf("%s;", curr_mpn);
                printf("%s;", curr_mfr);
                printf("%s;", curr_pkg);
                printf("%s;", curr_desc);
                printf("%s;", curr_proc);
                printf("%s\n", curr_note);

                designators = "";
                qty = 0;
            }

            notstarting = 1;
            if (designators != "") designators += ",";
            designators += E.name;

            curr_mpn  = mpn;
            curr_mfr  = mfr;
            curr_pkg  = replace_commas(E.package.name);
            curr_desc = desc;
            curr_proc = proc;
            curr_note = note;

            qty++;
        }

        // last line
        if (curr_mpn != "") {
            printf("%s;", designators);
            printf("%d;", qty);
            printf("%s;", curr_mpn);
            printf("%s;", curr_mfr);
            printf("%s;", curr_pkg);
            printf("%s;", curr_desc);
            printf("%s;", curr_proc);
            printf("%s\n", curr_note);
        }
    }

    dlgMessageBox(
        "Export complete:\n" +
        cpl_file + "\n" +
        bom_file,
        "Done"
    );

} else {
    dlgMessageBox("Run this ULP from a Board", "Error");
    exit(0);
}
